(defun c:my_rect( / )
(graphscr) (command "osnap" "none")
(setq ip (getpoint "Input the insertion point : ") )
( setq d0 (getreal "input variable d0") )
( setq d1 (getreal "input variable d1") )
( setq d2 (getreal "input variable d2") )
(setq p0 ip)
( setq p1 (polar p0 0.0 d0) )
( setq p2 (polar p1 1.5707963267948966 d1) )
( setq p3 (polar p2 3.141592653589793 d2) )
(command "pline" p0 p1 "A" p2 "L" p3 "A" "CL")
(princ)
);end-c:my_rect()
