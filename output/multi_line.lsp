(defun c:multi_line( / )
(command "erase" "all" "")
(graphscr) (command "osnap" "none")
(setq ip (getpoint "Input the insertion point : ") )
( setq r0 (getreal "\nInput ent0 radius <5.0>: ") )
(setq p0 ip)
(command "circle"  p0 r0)
(setq ip_x (getreal "Input x offset from the insertion point <30.0>: ") )
(setq ip_y (getreal "Input y offset from the insertion point <0.0>: ") )
(setq ip_o (rpoint ip ip_x ip_y))
( setq r0 (getreal "\nInput ent1 radius <5.0>: ") )
(setq p0 ip_o)
(command "circle"  p0 r0)
(setq ip_x (getreal "Input x offset from the insertion point <0.0>: ") )
(setq ip_y (getreal "Input y offset from the insertion point <-10.0>: ") )
(setq ip_o (rpoint ip ip_x ip_y))
( setq d0 (getreal "\nInput variable d0 <30.0>: ") )
( setq d1 (getreal "\nInput variable d1 <20.0>: ") )
( setq d2 (getreal "\nInput variable d2 <30.0>: ") )
(setq p0 ip_o)
( setq p1 (polar p0 0.0 d0) )
( setq p2 (polar p1 1.5707963267948966 d1) )
( setq p3 (polar p2 3.141592653589793 d2) )
(command "pline" p0 p1 "A" p2 "L" p3 "A" "CL")
(princ)
);end-c:multi_line()
