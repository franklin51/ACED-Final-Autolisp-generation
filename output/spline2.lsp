(defun c:my_spline2( / )
(command "erase" "all" "")
(graphscr) (command "osnap" "none")
(setq ip (getpoint "Input the insertion point : ") )
( setq d0 (getreal "\nInput variable d0 <0.067>: ") )
( setq d1 (getreal "\nInput variable d1 <0.069>: ") )
( setq d2 (getreal "\nInput variable d2 <0.172>: ") )
( setq d3 (getreal "\nInput variable d3 <0.106>: ") )
( setq d4 (getreal "\nInput variable d4 <0.253>: ") )
( setq d5 (getreal "\nInput variable d5 <0.15>: ") )
( setq d6 (getreal "\nInput variable d6 <0.501>: ") )
( setq d7 (getreal "\nInput variable d7 <0.415>: ") )
( setq d8 (getreal "\nInput variable d8 <0.839>: ") )
( setq d9 (getreal "\nInput variable d9 <0.438>: ") )
( setq d10 (getreal "\nInput variable d10 <0.653>: ") )
( setq d11 (getreal "\nInput variable d11 <0.251>: ") )
( setq d12 (getreal "\nInput variable d12 <0.369>: ") )
( setq d13 (getreal "\nInput variable d13 <0.138>: ") )
( setq d14 (getreal "\nInput variable d14 <0.212>: ") )
( setq d15 (getreal "\nInput variable d15 <0.081>: ") )
( setq d16 (getreal "\nInput variable d16 <0.165>: ") )
( setq d17 (getreal "\nInput variable d17 <0.096>: ") )
( setq d18 (getreal "\nInput variable d18 <0.251>: ") )
( setq d19 (getreal "\nInput variable d19 <0.161>: ") )
( setq d20 (getreal "\nInput variable d20 <0.375>: ") )
( setq d21 (getreal "\nInput variable d21 <0.219>: ") )
( setq d22 (getreal "\nInput variable d22 <0.468>: ") )
( setq d23 (getreal "\nInput variable d23 <0.253>: ") )
( setq d24 (getreal "\nInput variable d24 <0.621>: ") )
( setq d25 (getreal "\nInput variable d25 <0.378>: ") )
( setq d26 (getreal "\nInput variable d26 <0.674>: ") )
( setq d27 (getreal "\nInput variable d27 <0.306>: ") )
( setq d28 (getreal "\nInput variable d28 <0.39>: ") )
( setq d29 (getreal "\nInput variable d29 <0.129>: ") )
( setq d30 (getreal "\nInput variable d30 <0.178>: ") )
( setq d31 (getreal "\nInput variable d31 <0.065>: ") )
( setq d32 (getreal "\nInput variable d32 <0.062>: ") )
(setq p0 ip)
( setq p1 (polar p0 3.141592653589793 d0) )
( setq p2 (polar p1 -2.9284679270289744 d1) )
( setq p3 (polar p2 -2.6847264512737703 d2) )
( setq p4 (polar p3 -2.5096929121780938 d3) )
( setq p5 (polar p4 -2.3173197670796095 d4) )
( setq p6 (polar p5 -2.1787747746999164 d5) )
( setq p7 (polar p6 -2.0418215686017507 d6) )
( setq p8 (polar p7 -1.830886878596755 d7) )
( setq p9 (polar p8 -1.6345220030864207 d8) )
( setq p10 (polar p9 -1.4498865885050294 d9) )
( setq p11 (polar p10 -1.2579029354178177 d10) )
( setq p12 (polar p11 -1.0821334283819328 d11) )
( setq p13 (polar p12 -0.8975980242301751 d12) )
( setq p14 (polar p13 -0.6708294862411867 d13) )
( setq p15 (polar p14 -0.463668704712045 d14) )
( setq p16 (polar p15 -0.16366839866211225 d15) )
( setq p17 (polar p16 0.09869899524679235 d16) )
( setq p18 (polar p17 0.3393506426556856 d17) )
( setq p19 (polar p18 0.6279327414110543 d18) )
( setq p20 (polar p19 0.8175769327082596 d19) )
( setq p21 (polar p20 1.0129034096068328 d20) )
( setq p22 (polar p21 1.1554888762342939 d21) )
( setq p23 (polar p22 1.29213937167426 d22) )
( setq p24 (polar p23 1.4089117913287008 d23) )
( setq p25 (polar p24 1.5220111900549846 d24) )
( setq p26 (polar p25 1.6822651826864834 d25) )
( setq p27 (polar p26 1.8477712673134978 d26) )
( setq p28 (polar p27 2.0561720213712396 d27) )
( setq p29 (polar p28 2.277805598714884 d28) )
( setq p30 (polar p29 2.505980314897558 d29) )
( setq p31 (polar p30 2.711690255435285 d30) )
( setq p32 (polar p31 2.9397958473069106 d31) )
( setq p33 (polar p32 3.141592653589793 d32) )
(command "spline" p0 p1 p2 p3 p4 p5 p6 p7 p8 p9 p10 p11 p12 p13 p14 p15 p16 p17 p18 p19 p20 p21 p22 p23 p24 p25 p26 p27 p28 p29 p30 p31 p32 p33 """""")
(princ)
);end-c:my_spline2()
