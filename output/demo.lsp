(defun c:demo( / )
(command "erase" "all" "")
(graphscr) (command "osnap" "none")
(setq ip (getpoint "Input the insertion point : ") )
( setq r0 4.0)
(setq p0 ip)
(command "circle"  p0 r0)
(setq ip_x -30.0)
(setq ip_y -29.999999999999986)
(setq ip_o (rpoint ip ip_x ip_y))
( setq r0 4.0)
(setq p0 ip_o)
(command "circle"  p0 r0)
(setq ip_x -25.0 )
(setq ip_y -34.999999999999986 )
(setq ip_o (rpoint ip ip_x ip_y))
( setq d0 42.426)
( setq d1 14.142)
( setq d2 42.426)
( setq d3 14.142)
( setq a0 0.7853981633974481)
( setq a1 2.356194490192345)
( setq a2 -2.3561944901923453)
( setq a3 -0.7853981633974483)
(setq p0 ip_o)
( setq p1 (polar p0 0.7853981633974481 d0) )
( setq p2 (polar p1 2.356194490192345 d1) )
(setq th1 (* (atan 1.0 1.0) 4))
(setq An1 (rtd th1))
(setq AB (distance p1 p2))
(setq R1 (/ (/ AB 2.0) (sin (/ (abs th1) 2.0))))
( setq p3 (polar p2 -2.3561944901923453 d2) )
( setq p4 (polar p3 -0.7853981633974483 d3) )
(setq th3 (* (atan 1.0 1.0) 4))
(setq An3 (rtd th3))
(setq AB (distance p3 p4))
(setq R3 (/ (/ AB 2.0) (sin (/ (abs th3) 2.0))))
(command "pline" p0 p1 "arc" "R" R1 "Angle" An1 p2 "L" p3 "arc" "R" R3 "Angle" An3 p4 "")
(princ)
);end-c:demo()
