(defun c:my_rect( / )
(graphscr) (command "osnap" "none")
(setq ip (getpoint "Input the insertion point : ") )
( setq d1 (getreal "input variable d1") )
( setq d2 (getreal "input variable d2") )
( setq d3 (getreal "input variable d3") )
(setq p0 ip)
( setq p1 (polar p0 0.0 d1) )
( setq p2 (polar p1 1.5707963267948966 d2) )
( setq p3 (polar p2 3.141592653589793 d3) )
(command "pline" p0 p1 p2 p3 "c")
(princ)
);end-c:my_rect()
