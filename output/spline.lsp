(defun c:my_spline( / )
(command "erase" "all" "")
(graphscr) (command "osnap" "none")
; (setq ip (getpoint "Input the insertion point : ") )
; ( setq d0 (getreal "\nInput variable d0 <7.071>: ") )
; ( setq d1 (getreal "\nInput variable d1 <5.0>: ") )
; ( setq d2 (getreal "\nInput variable d2 <10.0>: ") )
; ( setq d3 (getreal "\nInput variable d3 <10.0>: ") )
(setq ip '(0 0) )
( setq d0 7.071 )
( setq d1 5.0 )
( setq d2 10.0 )
( setq d3 10.0 )
(setq p0 ip)
( setq p1 (polar p0 0.7853981633974483 d0) )
( setq p2 (polar p1 0.0 d1) )
( setq p3 (polar p2 -1.5707963267948966 d2) )
( setq p4 (polar p3 0.0 d3) )
; (setvar 'splmethod 1)
(command "b-spline")
; (command-s "SPLINE" "m" "cv" p0 p1 p2 p3 p4 "")
(princ)
);end-c:my_spline()
