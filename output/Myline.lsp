(defun c:my_line( / )
(command "erase" "all" "")
(graphscr) (command "osnap" "none")
(setq ip (getpoint "Input the insertion point : ") )
( setq d0 (getreal "Input Ent0 d0 <40.535>: ") )
( setq a0 (getreal "Input Ent0 a0 <0.7169389151061775>: ") )
(setq p0 ip)
( setq p1 (polar p0 a0 d0) )
(command "pline" p0 p1 "")
(princ)
);end-c:my_line()
