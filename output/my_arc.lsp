(defun c:top_curve( / )
; (command "erase" "all" "")
(graphscr) (command "osnap" "none")
(setq ip (getpoint "Input the insertion point : ") )
( setq d0 22.0)
( setq d1 22.0)
(setq p0 ip)
( setq p1 (polar p0 0.0 d0) )
( setq p2 (polar p1 3.141592653589793 d1) )
(setq th (* (atan (abs 0.763796)) 4))
(setq AB (distance p1 p2))
(setq R1 (/ (/ AB 2.0) (sin (/ th 2.0))))
(command "pline" p0 p1 "A" "R" R1 p2 "")
(princ)
);end-c:top_curve()
