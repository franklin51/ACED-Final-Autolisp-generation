(defun c:my_Pline( / )
(graphscr) (command "osnap" "none")
(setq ip (getpoint "Input the insertion point : ") )
( setq d0 (getreal "\nInput variable d0 <63.551>: ") )
( setq d1 (getreal "\nInput variable d1 <58.904>: ") )
( setq d2 (getreal "\nInput variable d2 <59.651>: ") )
( setq d3 (getreal "\nInput variable d3 <56.709>: ") )
( setq d4 (getreal "\nInput variable d4 <43.452>: ") )
( setq d5 (getreal "\nInput variable d5 <25.132>: ") )
(setq p0 ip)
( setq p1 (polar p0 0.8872101311909569 d0) )
( setq p2 (polar p1 2.4521294233132185 d1) )
( setq p3 (polar p2 -2.9983717376663925 d2) )
( setq p4 (polar p3 -1.9436710265817065 d3) )
( setq p5 (polar p4 0.12937302479554635 d4) )
( setq p6 (polar p5 -0.1651024303659343 d5) )
(command "pline" p0 p1 "A" p2 "L" p3 p4 "A" p5 p6 "L" "CL")
(princ)
);end-c:my_Pline()
