(defun c:example( / )
(command "erase" "all" "")
(graphscr) (command "osnap" "none")
(setq ip (getpoint "Input the insertion point : ") )
( setq d0 26.324)
( setq d1 10.435)
( setq d2 21.168)
(setq p0 ip)
( setq p1 (polar p0 -1.5707963267948966 d0) )
(setq th0 (* (atan 4.08592 1.0) 4))
(setq An0 (rtd th0))
(setq AB (distance p0 p1))
(setq R0 (/ (/ AB 2.0) (sin (/ (abs th0) 2.0))))
( setq p2 (polar p1 0.24963626748530965 d1) )
(setq th1 (* (atan -0.447242 1.0) 4))
(setq An1 (rtd th1))
(setq AB (distance p1 p2))
(setq R1 (/ (/ AB 2.0) (sin (/ (abs th1) 2.0))))
( setq p3 (polar p2 1.5707963267948966 d2) )
(setq th2 (* (atan 1.87636 1.0) 4))
(setq An2 (rtd th2))
(setq AB (distance p2 p3))
(setq R2 (/ (/ AB 2.0) (sin (/ (abs th2) 2.0))))
(command "pline" p0 "arc" "R" R0 "Angle" An0 p1 "arc" "R" R1 "Angle" An1 p2 "arc" "R" R2 "Angle" An2 p3 "arc" "R" R3 "Angle" An3 "CL")
(setq ip_x 35.021499999999996 )
(setq ip_y -4.043190000000001 )
(setq ip_o (rpoint ip ip_x ip_y))
( setq d0 3.258)
( setq d1 14.981)
( setq d2 3.258)
( setq d3 27.816)
( setq d4 3.967)
( setq d5 5.796)
( setq d6 2.814)
( setq d7 14.162)
( setq d8 2.814)
( setq d9 19.565)
( setq d10 2.814)
( setq d11 14.162)
( setq d12 2.814)
( setq d13 19.921)
( setq d14 2.814)
( setq d15 14.162)
( setq d16 2.814)
( setq d17 19.921)
( setq d18 2.814)
( setq d19 14.162)
( setq d20 2.814)
( setq d21 21.711)
( setq d22 2.814)
( setq d23 14.162)
( setq d24 2.814)
( setq d25 3.559)
( setq d26 3.967)
(setq p0 ip_o)
( setq p1 (polar p0 -0.5234456334296533 d0) )
(setq th0 (* (atan 0.295106 1.0) 4))
(setq An0 (rtd th0))
(setq AB (distance p0 p1))
(setq R0 (/ (/ AB 2.0) (sin (/ (abs th0) 2.0))))
( setq p2 (polar p1 -1.5707963267948966 d1) )
(setq th1 (* (atan -1.05179 1.0) 4))
(setq An1 (rtd th1))
(setq AB (distance p1 p2))
(setq R1 (/ (/ AB 2.0) (sin (/ (abs th1) 2.0))))
( setq p3 (polar p2 -2.61814702016014 d2) )
(setq th2 (* (atan 0.295106 1.0) 4))
(setq An2 (rtd th2))
(setq AB (distance p2 p3))
(setq R2 (/ (/ AB 2.0) (sin (/ (abs th2) 2.0))))
( setq p4 (polar p3 -2.8131859895465054 d3) )
(setq th3 (* (atan -0.404617 1.0) 4))
(setq An3 (rtd th3))
(setq AB (distance p3 p4))
(setq R3 (/ (/ AB 2.0) (sin (/ (abs th3) 2.0))))
( setq p5 (polar p4 -2.8598163255697373 d4) )
(setq th4 (* (atan 0.377722 1.0) 4))
(setq An4 (rtd th4))
(setq AB (distance p4 p5))
(setq R4 (/ (/ AB 2.0) (sin (/ (abs th4) 2.0))))
( setq p6 (polar p5 -2.2186798913992307 d5) )
(setq th5 (* (atan -0.0405975 1.0) 4))
(setq An5 (rtd th5))
(setq AB (distance p5 p6))
(setq R5 (/ (/ AB 2.0) (sin (/ (abs th5) 2.0))))
( setq p7 (polar p6 -1.811689404510486 d6) )
(setq th6 (* (atan 0.249025 1.0) 4))
(setq An6 (rtd th6))
(setq AB (distance p6 p7))
(setq R6 (/ (/ AB 2.0) (sin (/ (abs th6) 2.0))))
( setq p8 (polar p7 -2.5585311683289107 d7) )
(setq th7 (* (atan -0.710103 1.0) 4))
(setq An7 (rtd th7))
(setq AB (distance p7 p8))
(setq R7 (/ (/ AB 2.0) (sin (/ (abs th7) 2.0))))
( setq p9 (polar p8 2.977811117178978 d8) )
(setq th8 (* (atan 0.249025 1.0) 4))
(setq An8 (rtd th8))
(setq AB (distance p8 p9))
(setq R8 (/ (/ AB 2.0) (sin (/ (abs th8) 2.0))))
( setq p10 (polar p9 -3.09440422033586 d9) )
(setq th9 (* (atan -0.13948 1.0) 4))
(setq An9 (rtd th9))
(setq AB (distance p9 p10))
(setq R9 (/ (/ AB 2.0) (sin (/ (abs th9) 2.0))))
( setq p11 (polar p10 -2.883456741584961 d10) )
(setq th10 (* (atan 0.249025 1.0) 4))
(setq An10 (rtd th10))
(setq AB (distance p10 p11))
(setq R10 (/ (/ AB 2.0) (sin (/ (abs th10) 2.0))))
( setq p12 (polar p11 2.652897610464754 d11) )
(setq th11 (* (atan -0.710103 1.0) 4))
(setq An11 (rtd th11))
(setq AB (distance p11 p12))
(setq R11 (/ (/ AB 2.0) (sin (/ (abs th11) 2.0))))
( setq p13 (polar p12 1.9060673170125424 d12) )
(setq th12 (* (atan 0.249025 1.0) 4))
(setq An12 (rtd th12))
(setq AB (distance p12 p13))
(setq R12 (/ (/ AB 2.0) (sin (/ (abs th12) 2.0))))
( setq p14 (polar p13 2.1118491979789034 d13) )
(setq th13 (* (atan -0.142119 1.0) 4))
(setq An13 (rtd th13))
(setq AB (distance p13 p14))
(setq R13 (/ (/ AB 2.0) (sin (/ (abs th13) 2.0))))
( setq p15 (polar p14 2.3176360027100245 d14) )
(setq th14 (* (atan 0.249025 1.0) 4))
(setq An14 (rtd th14))
(setq AB (distance p14 p15))
(setq R14 (/ (/ AB 2.0) (sin (/ (abs th14) 2.0))))
( setq p16 (polar p15 1.5707963267948966 d15) )
(setq th15 (* (atan -0.710103 1.0) 4))
(setq An15 (rtd th15))
(setq AB (distance p15 p16))
(setq R15 (/ (/ AB 2.0) (sin (/ (abs th15) 2.0))))
( setq p17 (polar p16 0.8239566508797688 d16) )
(setq th16 (* (atan 0.249025 1.0) 4))
(setq An16 (rtd th16))
(setq AB (distance p16 p17))
(setq R16 (/ (/ AB 2.0) (sin (/ (abs th16) 2.0))))
( setq p18 (polar p17 1.02974345561089 d17) )
(setq th17 (* (atan -0.142119 1.0) 4))
(setq An17 (rtd th17))
(setq AB (distance p17 p18))
(setq R17 (/ (/ AB 2.0) (sin (/ (abs th17) 2.0))))
( setq p19 (polar p18 1.2355253365772507 d18) )
(setq th18 (* (atan 0.249025 1.0) 4))
(setq An18 (rtd th18))
(setq AB (distance p18 p19))
(setq R18 (/ (/ AB 2.0) (sin (/ (abs th18) 2.0))))
( setq p20 (polar p19 0.4886950431250392 d19) )
(setq th19 (* (atan -0.710103 1.0) 4))
(setq An19 (rtd th19))
(setq AB (distance p19 p20))
(setq R19 (/ (/ AB 2.0) (sin (/ (abs th19) 2.0))))
( setq p21 (polar p20 -0.25813591200483244 d20) )
(setq th20 (* (atan 0.249025 1.0) 4))
(setq An20 (rtd th20))
(setq AB (distance p20 p21))
(setq R20 (/ (/ AB 2.0) (sin (/ (abs th20) 2.0))))
( setq p22 (polar p21 -0.07853489620165649 d21) )
(setq th21 (* (atan -0.155495 1.0) 4))
(setq An21 (rtd th21))
(setq AB (distance p21 p22))
(setq R21 (/ (/ AB 2.0) (sin (/ (abs th21) 2.0))))
( setq p23 (polar p22 0.10110080965055532 d22) )
(setq th22 (* (atan 0.249025 1.0) 4))
(setq An22 (rtd th22))
(setq AB (distance p22 p23))
(setq R22 (/ (/ AB 2.0) (sin (/ (abs th22) 2.0))))
( setq p24 (polar p23 -0.6457550334636972 d23) )
(setq th23 (* (atan -0.710103 1.0) 4))
(setq An23 (rtd th23))
(setq AB (distance p23 p24))
(setq R23 (/ (/ AB 2.0) (sin (/ (abs th23) 2.0))))
( setq p25 (polar p24 -1.3925893660311026 d24) )
(setq th24 (* (atan 0.249025 1.0) 4))
(setq An24 (rtd th24))
(setq AB (distance p24 p25))
(setq R24 (/ (/ AB 2.0) (sin (/ (abs th24) 2.0))))
( setq p26 (polar p25 -0.9542634459493918 d25) )
(setq th25 (* (atan -0.0249071 1.0) 4))
(setq An25 (rtd th25))
(setq AB (distance p25 p26))
(setq R25 (/ (/ AB 2.0) (sin (/ (abs th25) 2.0))))
( setq p27 (polar p26 -0.28177632802005587 d26) )
(setq th26 (* (atan 0.377722 1.0) 4))
(setq An26 (rtd th26))
(setq AB (distance p26 p27))
(setq R26 (/ (/ AB 2.0) (sin (/ (abs th26) 2.0))))
(command "pline" p0 "arc" "R" R0 "Angle" An0 p1 "arc" "R" R1 "Angle" An1 p2 "arc" "R" R2 "Angle" An2 p3 "arc" "R" R3 "Angle" An3 p4 "arc" "R" R4 "Angle" An4 p5 "arc" "R" R5 "Angle" An5 p6 "arc" "R" R6 "Angle" An6 p7 "arc" "R" R7 "Angle" An7 p8 "arc" "R" R8 "Angle" An8 p9 "arc" "R" R9 "Angle" An9 p10 "arc" "R" R10 "Angle" An10 p11 "arc" "R" R11 "Angle" An11 p12 "arc" "R" R12 "Angle" An12 p13 "arc" "R" R13 "Angle" An13 p14 "arc" "R" R14 "Angle" An14 p15 "arc" "R" R15 "Angle" An15 p16 "arc" "R" R16 "Angle" An16 p17 "arc" "R" R17 "Angle" An17 p18 "arc" "R" R18 "Angle" An18 p19 "arc" "R" R19 "Angle" An19 p20 "arc" "R" R20 "Angle" An20 p21 "arc" "R" R21 "Angle" An21 p22 "arc" "R" R22 "Angle" An22 p23 "arc" "R" R23 "Angle" An23 p24 "arc" "R" R24 "Angle" An24 p25 "arc" "R" R25 "Angle" An25 p26 "arc" "R" R26 "Angle" An26 p27 "arc" "R" R27 "Angle" An27 "CL")
(setq ip_x 38.2213)
(setq ip_y -13.162)
(setq ip_o (rpoint ip ip_x ip_y))
( setq r0 3.5)
(setq p0 ip_o)
(command "circle"  p0 r0)
(setq ip_x -6.558900000000001)
(setq ip_y -41.5445)
(setq ip_o (rpoint ip ip_x ip_y))
( setq r0 3.5)
(setq p0 ip_o)
(command "circle"  p0 r0)
(setq ip_x -41.240700000000004)
(setq ip_y -43.1822)
(setq ip_o (rpoint ip ip_x ip_y))
( setq r0 3.5)
(setq p0 ip_o)
(command "circle"  p0 r0)
(setq ip_x -59.2787)
(setq ip_y -13.161999999999997)
(setq ip_o (rpoint ip ip_x ip_y))
( setq r0 3.5)
(setq p0 ip_o)
(command "circle"  p0 r0)
(setq ip_x -41.240700000000004)
(setq ip_y 16.858199999999997)
(setq ip_o (rpoint ip ip_x ip_y))
( setq r0 3.5)
(setq p0 ip_o)
(command "circle"  p0 r0)
(setq ip_x -4.817)
(setq ip_y 13.9916)
(setq ip_o (rpoint ip ip_x ip_y))
( setq r0 3.5)
(setq p0 ip_o)
(command "circle"  p0 r0)
(princ)
);end-c:example()
