(defun c:out_arrow( / )
(command "erase" "all" "")
(graphscr) (command "osnap" "none")
(setq ip (getpoint "Input the insertion point : ") )
( setq d0 3.692)
( setq d1 2.0)
( setq d2 2.5)
( setq d3 5.281)
( setq d4 5.281)
( setq d5 2.5)
( setq d6 2.0)
(setq p0 ip)
( setq p1 (polar p0 2.225311124957353 d0) )
(setq th (* (atan (abs 0.0655435)) 4))
(setq AB (distance p0 p1))
(setq R0 (/ (/ AB 2.0) (sin (/ th 2.0))))
( setq p2 (polar p1 0.6544914356285165 d1) )
( setq p3 (polar p2 2.2252896084330045 d2) )
( setq p4 (polar p3 -0.31209735036377334 d3) )
( setq p5 (polar p4 -1.520480482927617 d4) )
( setq p6 (polar p5 2.2252896084330014 d5) )
( setq p7 (polar p6 -2.4871012179612766 d6) )
(command "pline" p0 "A" "R" R0 p1 "L" p2 p3 p4 p5 p6 p7 "")
(princ)
);end-c:out_arrow()
